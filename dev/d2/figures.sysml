// SPDX-FileCopyrightText: 2026 tao3k team and Contributors
// SPDX-License-Identifier: Apache-2.0 AND LGPL-2.1-or-later

package ContextFigures {
    private import Views::*;
    private import StandardViewDefinitions::*;

    view context {
        expose AgenticAIContextArchitecture::ContextModule;
    }
    view session : StateTransitionView {
        expose AgenticAIContextLifecycle::SessionLifecycle;
    }
}
