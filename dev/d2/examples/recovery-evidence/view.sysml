// SPDX-FileCopyrightText: 2026 tao3k team and Contributors
// SPDX-License-Identifier: Apache-2.0 AND LGPL-2.1-or-later
package RecoveryEvidenceView {
 private import Views::*;
 private import StandardViewDefinitions::*;
 view teaching : InterconnectionView { expose ContextRepeatedRecovery::interruptedWriteDesign; }
}
